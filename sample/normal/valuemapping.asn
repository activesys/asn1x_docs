ValueMapping DEFINITIONS ::=
BEGIN
    Seq1 ::= SEQUENCE {
        a   INTEGER {one(1), two(2), three(3)}
    }
    Seq2 ::= SEQUENCE {
        a   INTEGER(0..9)
    }

    seq1 Seq1 ::= {a 100}
    seq2 Seq2 ::= seq1

    V ::= [0] INTEGER (0..30)
    W ::= [1] INTEGER (25..35)
    Y ::= [2] INTEGER (31..35)
    Z ::= V (Y | 24)
END

SetValueMapping DEFINITIONS
--AUTOMATIC TAGS
::=
BEGIN
    Set1 ::= SET {
        name    VisibleString,
        age     INTEGER
    }
    Set2 ::= SET {
        age     INTEGER,
        name    VisibleString
    }

    set1 Set1 ::= {name "wangbo", age 29}
    set2 Set2 ::= set1      -- incompatible
END
