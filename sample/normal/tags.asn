Tags
DEFINITIONS
AUTOMATIC TAGS
::=
BEGIN
    Int1 ::= [APPLICATION 0] EXPLICIT INTEGER
    Int2 ::= [PRIVATE 0] EXPLICIT INTEGER
    Int3 ::= [0] INTEGER
    Int4 ::= INTEGER
    Int5 ::= INTEGER
END
