E01112-1II DEFINITIONS ::=
BEGIN
    hs1 OCTET STRING ::= '0123456789ABCDEF'     -- E01112-1II
    hs2 OCTET STRING ::= '0123456789ABCDEF'  H  -- E01112-1II
    hs3 OCTET STRING ::= '0123456789ABCDEF'w    -- E01112-1II
    hs4 OCTET STRING ::= '0123456789ABCDEF'F    -- E01112-1II
END
