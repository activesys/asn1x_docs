E01110-II DEFINITIONS ::=
BEGIN
    bs1 BIT STRING ::= '00011111000011'b        -- E01110-II
    bs2 BIT STRING ::= '00011111000011'M        -- E01110-II
    bs3 BIT STRING ::= '00101111000001'         -- E01110-II
    bs4 BIT STRING ::= '00111111000011'    B    -- E01110-II
END
